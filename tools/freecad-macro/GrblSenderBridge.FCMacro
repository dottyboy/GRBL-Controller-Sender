"""GRBL Controller Sender bridge - FreeCAD macro (plan Phase 31).

Exports the current selection (or, if nothing is selected, every exportable
object in the active document) to a fixed temp SVG file via FreeCAD's own
real `Draft` module SVG exporter, then signals GRBL Controller Sender (if
running) to load it straight into its own SVG import tab - via the same
tagged Unix-FIFO message the Inkscape/QCAD bridges already define
("IMPORT_SVG:<path>", see src/protocol/usincrostart.pas in the main
GRBL-Controller-Sender repo). Reuses that exact message tag, no new import
path needed.

Targets FreeCAD's 2D drawing side (Draft/Sketcher geometry) - only objects
exposing a `.Shape` (Part::Feature-derived, importSVG's own documented
requirement) are exportable; parametric 3D solids have no meaningful
laser/CNC-2D equivalent and are silently skipped, not an error.
"""

import os

import FreeCAD
import FreeCADGui
import importSVG

SINCROSTART_FIFO = os.path.expanduser(
    '~/.config/GRBL-Controller-Sender/sincrostart.fifo')
EXPORT_PATH = '/tmp/grbl_sender_bridge.svg'


def send_sincrostart_message(line):
    """Non-blocking FIFO write - see the Inkscape/GIMP/Krita bridges' own
    copy of this same function for why (a blocking write would freeze
    FreeCAD's UI thread if GRBL Controller Sender isn't running)."""
    try:
        fd = os.open(SINCROSTART_FIFO, os.O_WRONLY | os.O_NONBLOCK)
    except OSError:
        return False
    try:
        os.write(fd, (line + '\n').encode('utf-8'))
        return True
    finally:
        os.close(fd)


def run():
    doc = FreeCAD.ActiveDocument
    if doc is None:
        FreeCAD.Console.PrintError(
            'GRBL Sender Bridge: no active document.\n')
        return

    selection = FreeCADGui.Selection.getSelection()
    export_list = selection if selection else list(doc.Objects)
    export_list = [obj for obj in export_list if hasattr(obj, 'Shape')]
    if not export_list:
        FreeCAD.Console.PrintError(
            'GRBL Sender Bridge: nothing exportable - select or create a '
            'Draft/Sketch/Part 2D object first.\n')
        return

    importSVG.export(export_list, EXPORT_PATH)

    if send_sincrostart_message('IMPORT_SVG:' + EXPORT_PATH):
        FreeCAD.Console.PrintMessage(
            'GRBL Sender Bridge: sent to GRBL Controller Sender: '
            + EXPORT_PATH + '\n')
    else:
        FreeCAD.Console.PrintWarning(
            'GRBL Sender Bridge: GRBL Controller Sender is not running - '
            'exported to ' + EXPORT_PATH + ' anyway, open it there '
            'manually.\n')


run()
